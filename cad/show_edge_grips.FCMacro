from pathlib import Path
import json
import FreeCAD as App
ROOT=Path(__file__).resolve().parents[1]
doc=App.openDocument(str(ROOT/'cad/pcb-vise.FCStd'))
rows=json.loads((ROOT/'cad/parts.json').read_text())
visible={r['name'] for r in rows if r['variant']=='main'}
for obj in doc.Objects:
    if obj.TypeId!='App::Part':obj.ViewObject.Visibility=obj.Name in visible
for name in ('Base','RotatingFrame','FixedJaw','SlidingJaw'):doc.getObject(name).ViewObject.Visibility=True
Gui.activeDocument().activeView().viewAxonometric()
Gui.activeDocument().activeView().fitAll()
doc.saveAs(str(ROOT/'cad/pcb-vise-edge-grips.FCStd'))
Gui.activeDocument().activeView().saveImage(str(ROOT/'exports/edge-grip-assembly.png'),1600,1200,'White')
